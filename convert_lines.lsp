(defun c:convert_lines ( / *error* lines pedit_accept)
  (defun *error* (message)
    (if (numberp pedit_accept)
      (setvar "PEDITACCEPT" pedit_accept)
    )
    (if (not (wcmatch (strcase message) "*BREAK*,*CANCEL*,*EXIT*"))
      (princ (strcat "\nError: " message))
    )
    (princ)
  )
  (if (setq lines (ssget '((0 . "LINE"))))
    (progn
      (setq pedit_accept (getvar "PEDITACCEPT"))
      (setvar "PEDITACCEPT" 1)
      (command-s "_.PEDIT" "_Multiple" lines "" "")
      (setvar "PEDITACCEPT" pedit_accept)
      (princ (strcat "\nProcessed " (itoa (sslength lines)) " selected line(s)."))
    )
    (princ "\nNo lines selected.")
  )
  (princ)
)
