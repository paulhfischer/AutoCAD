(defun c:door ( / _arc_point _frame_offset selection entity arc radius center startpoint endpoint anchor opposite offset)
  (defun _arc_point (data angle_code / center radius angle)
    (setq center (cdr (assoc 10 data)))
    (setq radius (cdr (assoc 40 data)))
    (setq angle (cdr (assoc angle_code data)))
    (list
      (+ (car center) (* radius (cos angle)))
      (+ (cadr center) (* radius (sin angle)))
      (caddr center)
    )
  )
  (defun _frame_offset (anchor center / scale)
    (setq scale (/ 0.4 (distance anchor center)))
    (mapcar (function (lambda (a b) (* scale (- b a)))) anchor center)
  )
  (while (setq selection (entsel "\nSelect door arc near an endpoint (Enter to finish): "))
    (setq entity (car selection))
    (setq arc (entget entity))
    (setq radius (cdr (assoc 40 arc)))
    (if (and (equal (cdr (assoc 0 arc)) "ARC") (numberp radius) (> radius 0))
      (progn
        (setq center (trans (cdr (assoc 10 arc)) entity 1))
        (setq startpoint (trans (_arc_point arc 50) entity 1))
        (setq endpoint (trans (_arc_point arc 51) entity 1))
        (if (<= (distance (cadr selection) startpoint) (distance (cadr selection) endpoint))
          (setq anchor startpoint opposite endpoint)
          (setq anchor endpoint opposite startpoint)
        )
        (setq offset (_frame_offset anchor center))
        (command-s "_.LINE" "_non" anchor "_non" center "")
        (command-s "_.LINE" "_non" center "_non" (mapcar '+ center offset) "")
        (command-s "_.LINE" "_non" opposite "_non" (mapcar '+ opposite offset) "")
      )
      (princ "\nSelect a circular arc with a positive radius.")
    )
  )
  (princ)
)
