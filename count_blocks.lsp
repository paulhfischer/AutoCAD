(defun c:count_blocks ( / _add_to_counter _format_entry blocks index blockname counter entry)
  (defun _add_to_counter (blockname counter / entry)
    (if (setq entry (assoc blockname counter))
      (subst (cons blockname (1+ (cdr entry))) entry counter)
      (cons (cons blockname 1) counter)
    )
  )

  (defun _format_entry (entry / key value dots)
    (setq key (car entry))
    (setq value (itoa (cdr entry)))
    (setq dots ".")
    (while (< (+ (strlen key) (strlen dots) (strlen value)) 80)
      (setq dots (strcat dots "."))
    )
    (strcat "\n" key dots value)
  )
  (if (setq blocks (ssget '((0 . "INSERT"))))
    (progn
      (repeat (setq index (sslength blocks))
        (setq blockname (cdr (assoc 2 (entget (ssname blocks (setq index (1- index)))))))
        (setq counter (_add_to_counter blockname counter))
      )
      (foreach entry (vl-sort counter (function (lambda (a b) (< (car a) (car b)))))
        (princ (_format_entry entry))
      )
    )
    (princ "\nNo blocks selected.")
  )
  (princ)
)
